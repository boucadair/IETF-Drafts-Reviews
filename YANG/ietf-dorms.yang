module ietf-dorms {
  yang-version 1.1;

  namespace "urn:ietf:params:xml:ns:yang:ietf-dorms";
  prefix "dorms";

  import ietf-inet-types {
    prefix "inet";
    reference
      "RFC 6991: Common YANG Data Types, Section 4";
  }

  import ietf-routing-types {
    prefix "rt-types";
    reference
      "RFC 8294: Common YANG Data Types for the Routing Area";
  }

  organization
    "IETF MBONED (Multicast Backbone Deployment) Working Group";
  contact
    "WG Web:   <https://datatracker.ietf.org/wg/mboned/>
     WG List:  <mailto:mboned@ietf.org>

     Author:   Jake Holland
               <mailto:jholland@akamai.com>";

  description
    "This module specifies a YANG module for DORMS.
     It provides out-of-band metadata about SSM channels.

     Copyright (c) 2025 IETF Trust and the persons identified as
     authors of the code. All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2025-09-15 {
    description
      "Initial version";
    reference
      "RFC XXXX: Discovery Of Restconf Metadata for Source-specific
                 Multicast";
  }

  container dorms {
    description
      "Top-level DORMS container.";
    container metadata {
      description
        "Metadata scaffold for source-specific multicast
         channels.";
      list sender {
        key address;
        description
          "Identifies a sender for DORMS.";

        leaf address {
          type inet:ip-address-no-zone;
          description
           "Specifies the source IP address of a multicast sender.";
        }

        list group {
          must '(re-match(./address, "[^:]*") and '
             +   're-match(../address, "[^:]*")) or '
             + '(re-match(./address, ".*:.*") and '
             +  're-match(../address, ".*:.*"))' {
            error-message
              'A group address type must match its parent source
               address type';
          }
          key address;
          description
            "Metadata for a DORMS (S,G).";
          leaf address {
            type rt-types:ip-multicast-group-address;
            description
              "Indicates the group IP address for an (S,G).";
          }
          list udp-stream {
            key "port";
            description
              "Metadata for UDP traffic on a specific port number.";
            leaf port {
              type inet:port-number;
              description
                "The UDP port number of a data stream.";
            }
          }
        }
      }
    }
  }
}
